;;; ============================================================
;;; SISTEM LAYERE URBANISM — Studio Office Kolectiv
;;; Conform legislatiei romanesti: L350/2001, RGU, PUG/PUZ/PUD
;;; Comanda: LAYERE-URB
;;; ============================================================

(defun C:LAYERE-URB ( / )
  (princ "\nCreare sistem layere Urbanism...")

  (defun make-layer (nume culoare tip-linie grosime descriere)
    (if (not (tblsearch "LAYER" nume))
      (progn
        (command "_.-LAYER" "_Make" nume "")
        (command "_.-LAYER" "_Color" culoare nume "")
        (if (tblsearch "LTYPE" tip-linie)
          (command "_.-LAYER" "_LType" tip-linie nume "")
        )
        (command "_.-LAYER" "_LWeight" grosime nume "")
        (command "_.-LAYER" "")
        (princ (strcat "\n  + " nume " — " descriere))
      )
      (princ (strcat "\n  ~ " nume " (existent)"))
    )
  )

  (foreach lt (list "DASHED" "DASHED2" "CENTER" "CENTER2" "PHANTOM" "HIDDEN" "DIVIDE")
    (if (not (tblsearch "LTYPE" lt))
      (command "_.-LINETYPE" "_Load" lt "acad.lin" "")
    )
  )

  (princ "\n--- LIMITE & PARCELE ---")
  (make-layer "U-LIMITA-UAT"         "1"   "Continuous" "0.70" "Limita unitatii administrativ-teritoriale")
  (make-layer "U-LIMITA-INTRAVILAN"  "1"   "DASHED"     "0.50" "Limita intravilan / extravilan")
  (make-layer "U-LIMITA-ZONA"        "2"   "DASHED2"    "0.35" "Limite zone functionale")
  (make-layer "U-LIMITA-SUBZONA"     "2"   "CENTER2"    "0.25" "Limite subzone functionale")
  (make-layer "U-PARCELA"            "7"   "Continuous" "0.35" "Limite parcele cadastrale")
  (make-layer "U-PARCELA-STUDIU"     "6"   "Continuous" "0.25" "Parcela / teren studiat")
  (make-layer "U-PARCELA-NR"         "7"   "Continuous" "0.18" "Numere cadastrale parcele")
  (make-layer "U-LOT"                "2"   "Continuous" "0.35" "Loturi propuse prin PUZ/PUD")

  (princ "\n--- CONSTRUCTII ---")
  (make-layer "U-CONST-EXISTENTA"    "8"   "Continuous" "0.35" "Constructii existente")
  (make-layer "U-CONST-MENTINUTA"    "3"   "Continuous" "0.35" "Constructii de mentinut")
  (make-layer "U-CONST-PROPUSA"      "4"   "Continuous" "0.50" "Constructii propuse")
  (make-layer "U-CONST-DEMOLARE"     "1"   "DASHED"     "0.25" "Constructii de demolat")
  (make-layer "U-CONST-ISTORICA"     "2"   "Continuous" "0.35" "Monumente si cladiri istorice")
  (make-layer "U-CONST-INDUSTRIALA"  "8"   "Continuous" "0.25" "Constructii industriale / depozitare")
  (make-layer "U-CONST-PARTER"       "8"   "Continuous" "0.25" "Amprenta la sol constructii")

  (princ "\n--- REGLEMENTARI URBANISTICE ---")
  (make-layer "U-POT-EXISTENT"       "8"   "DASHED2"    "0.18" "Procent ocupare teren existent")
  (make-layer "U-POT-PROPUS"         "4"   "Continuous" "0.25" "POT propus")
  (make-layer "U-REGIM-INALTIME"     "6"   "Continuous" "0.25" "Regim de inaltime")
  (make-layer "U-ALINIERE"           "1"   "CENTER"     "0.25" "Linia de aliniere stradala")
  (make-layer "U-RETRAGERE-FRONT"    "2"   "DASHED"     "0.25" "Retragere minima fata de strada")
  (make-layer "U-RETRAGERE-LATERAL"  "2"   "DASHED2"    "0.18" "Retrageri laterale")
  (make-layer "U-RETRAGERE-SPATE"    "2"   "DASHED2"    "0.18" "Retragere posterioara")
  (make-layer "U-SERVITUTE"          "1"   "PHANTOM"    "0.18" "Servituti de utilitate publica")
  (make-layer "U-ZONA-PROTECTIE"     "1"   "PHANTOM"    "0.25" "Zone de protectie (HV, CF, apa)")

  (princ "\n--- ZONE FUNCTIONALE ---")
  (make-layer "U-ZF-REZIDENTIAL"     "2"   "Continuous" "0.18" "Zona rezidentiala (L)")
  (make-layer "U-ZF-MIXTA"           "6"   "Continuous" "0.18" "Zona mixta (M)")
  (make-layer "U-ZF-COMERCIAL"       "2"   "Continuous" "0.18" "Zona servicii / comert (C)")
  (make-layer "U-ZF-PRODUCTIE"       "252" "Continuous" "0.18" "Zona productie / depozitare (I)")
  (make-layer "U-ZF-INSTITUTII"      "1"   "Continuous" "0.18" "Institutii publice (IS)")
  (make-layer "U-ZF-SPATII-VERZI"    "3"   "Continuous" "0.18" "Spatii verzi publice (V)")
  (make-layer "U-ZF-SPORT"           "3"   "Continuous" "0.18" "Sport si agrement")
  (make-layer "U-ZF-CIMITIR"         "82"  "Continuous" "0.18" "Cimitire")
  (make-layer "U-ZF-GOSPODARIE"      "8"   "Continuous" "0.18" "Gospodarie comunala")
  (make-layer "U-ZF-PADURE"          "3"   "Continuous" "0.18" "Paduri si silvicultura")
  (make-layer "U-ZF-AGRICOL"         "82"  "Continuous" "0.18" "Teren agricol")
  (make-layer "U-ZF-RESTRICTIE"      "1"   "DASHED"     "0.18" "Zone cu restrictii de constructibilitate")

  (princ "\n--- CIRCULATIE ---")
  (make-layer "U-CAROSABIL"          "8"   "Continuous" "0.35" "Carosabil — strazi existente")
  (make-layer "U-CAROSABIL-PROPUS"   "4"   "Continuous" "0.35" "Strazi propuse")
  (make-layer "U-TROTUARE"           "8"   "Continuous" "0.18" "Trotuare si alei pietonale")
  (make-layer "U-PISTE-CICLO"        "3"   "Continuous" "0.18" "Piste pentru ciclistiisti")
  (make-layer "U-PARCAJE"            "8"   "DASHED2"    "0.18" "Parcaje si garaje")
  (make-layer "U-CF-FERATA"          "7"   "Continuous" "0.50" "Cale ferata")
  (make-layer "U-AEROPORT"           "7"   "Continuous" "0.25" "Aeroport si heliport")
  (make-layer "U-NR-IMOBIL"          "8"   "Continuous" "0.18" "Numere imobile / adrese postale")

  (princ "\n--- RETELE TEHNICO-EDILITARE ---")
  (make-layer "U-RETEA-AP"           "5"   "Continuous" "0.25" "Retea alimentare cu apa")
  (make-layer "U-RETEA-CA"           "5"   "DASHED"     "0.25" "Retea canalizare ape uzate")
  (make-layer "U-RETEA-AP-PL"        "5"   "DASHED2"    "0.18" "Canalizare ape pluviale")
  (make-layer "U-RETEA-EL-JT"        "2"   "Continuous" "0.25" "Retea electrica joasa tensiune")
  (make-layer "U-RETEA-EL-MT"        "2"   "DASHED"     "0.35" "Retea electrica medie tensiune")
  (make-layer "U-RETEA-EL-AERIANA"   "2"   "CENTER"     "0.25" "Retea electrica aeriana")
  (make-layer "U-RETEA-GZ"           "1"   "Continuous" "0.25" "Retea distributie gaz")
  (make-layer "U-RETEA-TC"           "6"   "Continuous" "0.18" "Retea telecomunicatii / fibra optica")
  (make-layer "U-RETEA-TERMICA"      "1"   "DASHED"     "0.18" "Retea termica district")
  (make-layer "U-STATII-POMPARE"     "5"   "Continuous" "0.25" "Statii pompare si tratare")

  (princ "\n--- TOPOGRAFIE & RIDICARI ---")
  (make-layer "U-CURBE-NIVEL"        "82"  "Continuous" "0.18" "Curbe de nivel principale")
  (make-layer "U-CURBE-NIVEL-SEC"    "82"  "Continuous" "0.09" "Curbe de nivel secundare")
  (make-layer "U-COTE-TEREN"         "82"  "Continuous" "0.18" "Cote altimetrice teren")
  (make-layer "U-PUNCTE-TOPO"        "82"  "Continuous" "0.18" "Puncte de reper topografice")
  (make-layer "U-HIDRO"              "5"   "Continuous" "0.35" "Ape — rauri lacuri canale")
  (make-layer "U-PADURE-EX"          "3"   "Continuous" "0.18" "Padure si vegetatie existenta")

  (princ "\n--- ADNOTARI ---")
  (make-layer "U-COTA"               "2"   "Continuous" "0.18" "Cote dimensionale")
  (make-layer "U-TEXT"               "7"   "Continuous" "0.18" "Texte si note")
  (make-layer "U-LEGENDA"            "7"   "Continuous" "0.18" "Legenda plan")
  (make-layer "U-SIMBOL"             "7"   "Continuous" "0.18" "Simboluri conventionale")
  (make-layer "U-NORD"               "7"   "Continuous" "0.35" "Sageata nord")
  (make-layer "U-SCARA-GRAFICA"      "7"   "Continuous" "0.25" "Scara grafica")
  (make-layer "U-HAŞURA-ZF"          "253" "Continuous" "0.09" "Hasuri zone functionale")

  (princ "\n--- CADRU PLANŞA ---")
  (make-layer "U-CADRU"              "7"   "Continuous" "0.70" "Cadru planşa")
  (make-layer "U-INDICATOR"          "7"   "Continuous" "0.35" "Tabel indicator")
  (make-layer "U-VIEWPORT"           "8"   "Continuous" "0.18" "Viewporturi layout")
  (make-layer "U-XREF"               "8"   "Continuous" "0.18" "Referinte externe")
  (make-layer "U-ORTOFOTO"           "8"   "Continuous" "0.09" "Ortofotoplan referinta")

  (command "_.-LAYER" "_Set" "U-PARCELA-STUDIU" "")

  (princ "\n\nSistem layere URBANISM creat cu succes!")
  (princ "\nLayer curent: U-PARCELA-STUDIU")
  (princ)
)

(princ "\nLayere Urbanism incarcate. Comanda: LAYERE-URB")
(princ)
